AMDGPU-MIB DEFINITIONS ::= BEGIN

IMPORTS
    OBJECT-TYPE, MODULE-IDENTITY,
    enterprises, Unsigned32, Counter64
    FROM SNMPv2-SMI

    TEXTUAL-CONVENTION, DisplayString, TruthValue
    FROM SNMPv2-TC;

Thousand ::= TEXTUAL-CONVENTION
    DISPLAY-HINT "d-3"
    STATUS       current
    DESCRIPTION  "Scaled by 1000."
    SYNTAX       Integer32

doubleagentx MODULE-IDENTITY
    LAST-UPDATED "202508241642Z"
    ORGANIZATION "Double AgentX"
    CONTACT-INFO
        "This mib is maintained by doubleagentx"
    DESCRIPTION "Provide status values to monitor AMDGPU."
    ::= { enterprises 3334444 }

amdgpu OBJECT-TYPE
    SYNTAX SEQUENCE OF amdgpuEntry
    ACCESS read-only
    STATUS current
    DESCRIPTION "AMDGPU information."
    ::= { doubleagentx 1 }

amdgpuMeta OBJECT-TYPE
    SYNTAX amdgpuMeta
    ACCESS read-only
    STATUS current
    DESCRIPTION "Meta-information on AMDGPU."
    ::= { amdgpu 1 }

amdgpuMeta ::= SEQUENCE {
    ModuleVersion DisplayString
    UtilsVersion DisplayString
}

ModuleVersion OBJECT-TYPE
    SYNTAX DisplayString
    MAX-ACCESS read-only
    STATUS current
    DESCRIPTION "Version of the loaded kernel module"
    ::= { amdgpuMeta 1 }

UtilsVersion OBJECT-TYPE
    SYNTAX DisplayString
    MAX-ACCESS read-only
    STATUS current
    DESCRIPTION "Version of amdgpu-utils"
    ::= { amdgpuMeta 2 }

amdgpuTable OBJECT-TYPE
    SYNTAX SEQUENCE OF amdgpuEntry
    MAX-ACCESS read-only
    STATUS current
    DESCRIPTION "An table containing AMDGPU devices and its statistics."
    INDEX { amdgpuMinor }
    ::= { amdgpu 2 }

amdgpuEntry OBJECT-TYPE
    SYNTAX amdgpuEntry
    MAX-ACCESS read-only
    STATUS current
    DESCRIPTION "An entry containing a AMDGPU device and its statistics."
    INDEX { amdgpuMinor }
    ::= { amdgpuTable 1 }

amdgpuEntry ::= SEQUENCE {
    Minor INTEGER
    DeviceName DisplayString
    DeviceId DisplayString
    DeviceRev DisplayString
    SubsystemId DisplayString
    GUID DisplayString
    UniqueId DisplayString
    VbiosVersion DisplayString
    TemperatureSensorEdge Thousand
    TemperatureSensorJunction Thousand
    TemperatureSensorMemory Thousand
    DcefclkClockSpeed INTEGER
    DcefclkClockLevel INTEGER
    FclkClockSpeed INTEGER
    FclkClockLevel INTEGER
    MclkClockSpeed INTEGER
    MclkClockLevel INTEGER
    SclkClockSpeed INTEGER
    SclkClockLevel INTEGER
    SocclkClockSpeed INTEGER
    SocclkClockLevel INTEGER
    PcieClockLevel INTEGER
    PerformanceLevel DisplayString
    MaxGraphicsPackagePower Thousand
    AverageGraphicsPackagePower Thousand
    GpuUse Thousand
    GpuMemoryAllocated Thousand
    GpuMemoryReadWriteActivity Thousand
}

Minor OBJECT-TYPE
    SYNTAX INTEGER
    MAX-ACCESS read-only
    STATUS current
    DESCRIPTION "The AMDGPU minor number"
    ::= { amdgpuEntry 1 }

DeviceName OBJECT-TYPE
    SYNTAX DisplayString
    MAX-ACCESS read-only
    STATUS current
    DESCRIPTION "Name of the Resource the minor belongs to"
    ::= { amdgpuEntry 2 }

DeviceId OBJECT-TYPE
    SYNTAX DisplayString
    MAX-ACCESS read-only
    STATUS current
    DESCRIPTION "ID of the device"
    ::= { amdgpuEntry 3 }

DeviceRev OBJECT-TYPE
    SYNTAX DisplayString
    MAX-ACCESS read-only
    STATUS current
    DESCRIPTION "Revision of the device"
    ::= { amdgpuEntry 4 }

SubsystemId OBJECT-TYPE
    SYNTAX DisplayString
    MAX-ACCESS read-only
    STATUS current
    DESCRIPTION "Subsystem ID of the device"
    ::= { amdgpuEntry 5 }

GUID OBJECT-TYPE
    SYNTAX DisplayString
    MAX-ACCESS read-only
    STATUS current
    DESCRIPTION "GUID of the device"
    ::= { amdgpuEntry 6 }

UniqueId OBJECT-TYPE
    SYNTAX DisplayString
    MAX-ACCESS read-only
    STATUS current
    DESCRIPTION "Unique ID of the device"
    ::= { amdgpuEntry 7 }

VbiosVersion OBJECT-TYPE
    SYNTAX DisplayString
    MAX-ACCESS read-only
    STATUS current
    DESCRIPTION "The promotion score of a resource"
    ::= { amdgpuEntry 8 }

TemperatureSensorEdge OBJECT-TYPE
    SYNTAX Thousand
    UNITS "C"
    ACCESS read-only
    STATUS current
    DESCRIPTION "Temperature of the device at the edge"
    ::= { amdgpuEntry 9 }

TemperatureSensorJunction OBJECT-TYPE
    SYNTAX Thousand
    UNITS "C"
    MAX-ACCESS read-only
    STATUS current
    DESCRIPTION "Temperature of the device at the junction"
    ::= { amdgpuEntry 10 }

TemperatureSensorMemory OBJECT-TYPE
    SYNTAX Thousand
    UNITS "C"
    MAX-ACCESS read-only
    STATUS current
    DESCRIPTION "Temperature of the device at the memory"
    ::= { amdgpuEntry 11 }

DcefclkClockSpeed OBJECT-TYPE
    SYNTAX INTEGER
    UNITS "MHz"
    MAX-ACCESS read-only
    STATUS current
    DESCRIPTION "dcefclk clock speed"
    ::= { amdgpuEntry 12 }

DcefclkClockLevel OBJECT-TYPE
    SYNTAX INTEGER
    MAX-ACCESS read-only
    STATUS current
    DESCRIPTION "dcefclk clock level"
    ::= { amdgpuEntry 13 }

FclkClockSpeed OBJECT-TYPE
    SYNTAX INTEGER
    UNITS "MHz"
    MAX-ACCESS read-only
    STATUS current
    DESCRIPTION "fclk clock speed"
    ::= { amdgpuEntry 14 }

FclkClockLevel OBJECT-TYPE
    SYNTAX INTEGER
    MAX-ACCESS read-only
    STATUS current
    DESCRIPTION "dcefclk clock level"
    ::= { amdgpuEntry 15 }

MclkClockSpeed OBJECT-TYPE
    SYNTAX INTEGER
    UNITS "MHz"
    MAX-ACCESS read-only
    STATUS current
    DESCRIPTION "mclk clock speed"
    ::= { amdgpuEntry 16 }

MclkClockLevel OBJECT-TYPE
    SYNTAX INTEGER
    MAX-ACCESS read-only
    STATUS current
    DESCRIPTION "mclk clock level"
    ::= { amdgpuEntry 17 }

SclkClockSpeed OBJECT-TYPE
    SYNTAX INTEGER
    UNITS "MHz"
    MAX-ACCESS read-only
    STATUS current
    DESCRIPTION "mclk clock speed"
    ::= { amdgpuEntry 18 }

SclkClockLevel OBJECT-TYPE
    SYNTAX INTEGER
    MAX-ACCESS read-only
    STATUS current
    DESCRIPTION "sclk clock level"
    ::= { amdgpuEntry 19 }

SocclkClockSpeed OBJECT-TYPE
    SYNTAX INTEGER
    UNITS "MHz"
    MAX-ACCESS read-only
    STATUS current
    DESCRIPTION "mclk clock speed"
    ::= { amdgpuEntry 20 }

SocclkClockLevel OBJECT-TYPE
    SYNTAX INTEGER
    MAX-ACCESS read-only
    STATUS current
    DESCRIPTION "socclk clock level"
    ::= { amdgpuEntry 21 }

PcieClockLevel OBJECT-TYPE
    SYNTAX INTEGER
    MAX-ACCESS read-only
    STATUS current
    DESCRIPTION "pcie clock level"
    ::= { amdgpuEntry 22 }

PerformanceLevel OBJECT-TYPE
    SYNTAX INTEGER
    MAX-ACCESS read-only
    STATUS current
    DESCRIPTION "Performance Level"
    ::= { amdgpuEntry 23 }

MaxGraphicsPackagePower OBJECT-TYPE
    SYNTAX Thousand
    UNITS "Watts"
    MAX-ACCESS read-only
    STATUS current
    DESCRIPTION "Performance Level"
    ::= { amdgpuEntry 24 }

AverageGraphicsPackagePower OBJECT-TYPE
    SYNTAX Thousand
    UNITS "Watts"
    MAX-ACCESS read-only
    STATUS current
    DESCRIPTION "Average Graphics Package Power"
    ::= { amdgpuEntry 25 }

GpuUse OBJECT-TYPE
    SYNTAX Thousand
    UNITS "%"
    MAX-ACCESS read-only
    STATUS current
    DESCRIPTION "GPU use"
    ::= { amdgpuEntry 26 }

GpuMemoryAllocated OBJECT-TYPE
    SYNTAX Thousand
    UNITS "%"
    MAX-ACCESS read-only
    STATUS current
    DESCRIPTION "GPU Memory Allocated (VRAM%)"
    ::= { amdgpuEntry 27 }

GpuMemoryReadWriteActivity OBJECT-TYPE
    SYNTAX Thousand
    UNITS "%"
    MAX-ACCESS read-only
    STATUS current
    DESCRIPTION "GPU Memory Read/Write Activity"
    ::= { amdgpuEntry 28 }


END
